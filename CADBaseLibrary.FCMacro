#!/usr/bin/env python
# -*- coding: utf-8 -*-

#***************************************************************************
#*                                                                         *
#*   Copyright (c) 2022 Ivan <in@cadbase.rs>              *
#*                                                                         *
#*   This program is free software; you can redistribute it and/or modify  *
#*   it under the terms of the GNU Lesser General Public License (LGPL)    *
#*   as published by the Free Software Foundation; either version 2 of     *
#*   the License, or (at your option) any later version.                   *
#*   for detail see the LICENCE text file.                                 *
#*                                                                         *
#*   This program is distributed in the hope that it will be useful,       *
#*   but WITHOUT ANY WARRANTY; without even the implied warranty of        *
#*   MERCHANTABILITY or FITNESS FOR A PARTICULAR PURPOSE.  See the         *
#*   GNU Library General Public License for more details.                  *
#*                                                                         *
#*   You should have received a copy of the GNU Library General Public     *
#*   License along with this program; if not, write to the Free Software   *
#*   Foundation, Inc., 59 Temple Place, Suite 330, Boston, MA  02111-1307  *
#*   USA                                                                   *
#*                                                                         *
#***************************************************************************
from __future__ import print_function

__title__="FreeCAD CADBase Library Macro"

'''
Macro for integration of CADBase with FreeCAD


INSTALLATION

This script is made to be used as a FreeCAD macro, and to be placed
inside your macros folder (default is $HOME/.FreeCAD on mac/linux,
C:/Users/youruser/Application Data/FreeCAD on windows).

After it is installed on the above location, it will be available
in the macros menu. On first run, it will ask you for the location
of your library.


USAGE

This macro adds a browser window to the FreeCAD interface, from
which you can browse and install items from the library.
'''

import sys, FreeCAD, FreeCADGui, Part, zipfile, tempfile, Mesh, os, subprocess, json, time
from multiprocessing import cpu_count
from multiprocessing.pool import ThreadPool
from types import SimpleNamespace
from PySide import QtGui, QtCore
from PySide2 import QtNetwork

param = FreeCAD.ParamGet('User parameter:Plugins/cadbase_library')
s = param.GetString('destination')
api = param.GetString('api-url')
token = param.GetString('auth-token')
api_login = 'https://api.cadbase.rs/login'
cdbs_api = "https://api.cadbase.rs/graphql"
user_agent = b'Mozilla/5.0 (Macintosh; Intel Mac OS 10 12.3; rv:42.0) Gecko/20100101 Firefox/42.0'
content_type = b"application/json"
RESPONSEFILE = 'response'
# print('User parameter:Plugins/partlib : destination : ',s)

try:
    QtCore.QTextCodec.setCodecForTr(QTextCodec.codecForName("UTF-8"))
except:
    pass # Will fallback to Latin-1

if s:
    LIBRARYPATH = s
else:

    # folderDialog = App.getUserAppDataDir()+"Mod/cadbase_library"

    # if not os.path.exists(folderDialog):
    #     os.mkdir(folderDialog)

    # if not os.path.isdir(folderDialog):
    #     folderDialog = QtGui.QFileDialog.getExistingDirectory(None,QtGui.QApplication.translate("CADBaseLibrary", "Location of your existing CADBase library"))

    folderDialog = QtGui.QFileDialog.getExistingDirectory(None,QtGui.QApplication.translate("CADBaseLibrary", "Location of your existing CADBase library"))
    param.SetString('destination',folderDialog.replace("\\","/")) # forward slashes apparently work on windows too
    LIBRARYPATH = param.GetString('destination')

if not api:
    param.SetString('api-url', cdbs_api)

if not token:
    param.SetString('auth-token', '')

def translate(context, text):

    # Will fallback to Latin-1
    return QtGui.QApplication.translate(context, text)

class ExpFileSystemModel(QtGui.QFileSystemModel):
    "a custom QFileSystemModel that displays freecad file icons"
    def __init__(self):
        QtGui.QFileSystemModel.__init__(self)

    def data(self, index, role):
        if index.column() == 0 and role == QtCore.Qt.DecorationRole:
            if index.data().lower().endswith('.fcstd'):
                return QtGui.QIcon(':icons/freecad-doc.png')
            elif index.data().lower() == "private":
                return QtGui.QIcon.fromTheme("folder-lock")
        return super(ExpFileSystemModel, self).data(index, role)

class ExpDockWidget(QtGui.QDockWidget):
    "a library explorer dock widget"

    def __init__(self,LIBRARYPATH):
        QtGui.QDockWidget.__init__(self)

        self.setObjectName("CADBaseLibrary")

        # setting up a directory model that shows only fcstd, step and brep
        self.dirmodel = ExpFileSystemModel()
        self.dirmodel.setRootPath(LIBRARYPATH)
        self.dirmodel.setNameFilters(["*.fcstd","*.FcStd","*.FCSTD","*.stp","*.STP","*.step","*.STEP", "*.brp", "*.BRP", "*.brep", "*.BREP"])
        self.dirmodel.setNameFilterDisables(0)

        self.folder = QtGui.QTreeView()
        self.folder.setModel(self.dirmodel)
        self.folder.clicked[QtCore.QModelIndex].connect(self.clicked)
        self.folder.doubleClicked[QtCore.QModelIndex].connect(self.doubleclicked)
        # Don't show columns for size, file type, and last modified
        self.folder.setHeaderHidden(True)
        self.folder.hideColumn(1)
        self.folder.hideColumn(2)
        self.folder.hideColumn(3)
        self.folder.setRootIndex(self.dirmodel.index(LIBRARYPATH))

        self.preview = QtGui.QLabel()
        self.preview.setFixedHeight(128)

        self.updatebutton = QtGui.QPushButton()
        icon = QtGui.QIcon.fromTheme("emblem-synchronizing")
        self.updatebutton.setIcon(icon)
        self.updatebutton.clicked.connect(self.updatelibrary)
        self.updatebutton.hide()

        self.configbutton = QtGui.QPushButton()
        icon = QtGui.QIcon.fromTheme("emblem-system")
        self.configbutton.setIcon(icon)
        self.configbutton.clicked.connect(self.setconfig)
        self.configbutton.hide()

        self.formatLabel = QtGui.QLabel()
        self.formatLabel.hide()

        self.prevbutton = QtGui.QPushButton()
        self.prevbutton.clicked.connect(self.showpreview)
        self.prevbutton.setStyleSheet("text-align: left;")

        self.optbutton = QtGui.QPushButton()
        self.optbutton.clicked.connect(self.showoptions)
        self.optbutton.setStyleSheet("text-align: left;")

        self.fcstdCB = QtGui.QCheckBox('FCStd')
        self.fcstdCB.setCheckState(QtCore.Qt.Checked)
        self.fcstdCB.setEnabled(False)
        self.fcstdCB.hide()
        self.stepCB = QtGui.QCheckBox('STEP')
        self.stepCB.setCheckState(QtCore.Qt.Checked)
        self.stepCB.hide()
        self.stlCB = QtGui.QCheckBox('STL')
        self.stlCB.setCheckState(QtCore.Qt.Checked)
        self.stlCB.hide()

        container = QtGui.QWidget()
        grid = QtGui.QGridLayout()
        grid.setSpacing(10)

        grid.addWidget(self.folder,0,0,1,2)
        grid.addWidget(self.prevbutton,1,0,1,2)
        grid.addWidget(self.preview,2,0,1,2)
        grid.addWidget(self.optbutton,3,0,1,2)

        grid.addWidget(self.updatebutton,4,0,1,1)
        grid.addWidget(self.configbutton,4,1,1,1)
        grid.addWidget(self.formatLabel,5,0,1,2)
        grid.addWidget(self.fcstdCB,6,0,1,2)
        grid.addWidget(self.stepCB,7,0,1,2)
        grid.addWidget(self.stlCB,8,0,1,2)

        self.retranslateUi()
        container.setLayout(grid)
        self.setWidget(container)

    def retranslateUi(self):
        self.setWindowTitle(translate("CADBaseLibrary", "CADBase Library"))
        self.updatebutton.setText(translate("CADBaseLibrary", "Update from CADBase"))
        self.configbutton.setText(translate("CADBaseLibrary", "Config"))
        self.formatLabel.setText(translate("CADBaseLibrary", "Add to library"))
        self.optbutton.setText(translate("CADBaseLibrary", "Options ⏷"))
        self.prevbutton.setText(translate("CADBaseLibrary", "Preview ⏶"))

    def clicked(self, index):
        path = self.dirmodel.filePath(index)

        if path.lower().endswith(".fcstd"):
            zfile=zipfile.ZipFile(path)
            files=zfile.namelist()
            # check for meta-file if it's really a FreeCAD document
            if files[0] == "Document.xml":
                image="thumbnails/Thumbnail.png"
                if image in files:
                    image=zfile.read(image)
                    thumbfile = tempfile.mkstemp(suffix='.png')[1]
                    thumb = open(thumbfile,"wb")
                    thumb.write(image)
                    thumb.close()
                    im = QtGui.QPixmap(thumbfile)
                    self.preview.setPixmap(im)
                    return

        self.preview.clear()

    def doubleclicked(self, index):
        path = self.dirmodel.filePath(index)

        if os.path.isdir(path):

            if param.GetString('auth-token'):

                component_file = path + '/component'

                if os.path.exists(component_file):
                    # FreeCAD.Console.PrintWarning('component\n')

                    data_file = open(component_file, 'r')
                    component_data = json.loads(data_file.read(), object_hook=lambda d: SimpleNamespace(**d))
                    FreeCAD.Console.PrintWarning('Select component: ')
                    FreeCAD.Console.PrintWarning(component_data.uuid)
                    FreeCAD.Console.PrintWarning('/n')
                    data_file.close()

                    CDBSApi(QueriesAPI.componentModifications(component_data.uuid), LIBRARYPATH)
                    updateComponent(LIBRARYPATH, path)

                modification_file = path + '/modification'

                if os.path.exists(modification_file):
                    # FreeCAD.Console.PrintWarning('modification\n')

                    data_file = open(modification_file, 'r')
                    modification_data = json.loads(data_file.read(), object_hook=lambda d: SimpleNamespace(**d))
                    FreeCAD.Console.PrintWarning('Select modification: ')
                    FreeCAD.Console.PrintWarning(modification_data.uuid)
                    FreeCAD.Console.PrintWarning('\n')
                    data_file.close()

                    CDBSApi(QueriesAPI.targetFileset(modification_data.uuid), LIBRARYPATH)
                    updateComponentModificaion(LIBRARYPATH, path, modification_data.uuid)

            else:

                FreeCAD.Console.PrintWarning('Token not found')

        else:

            if path.lower().endswith(".stp") or path.lower().endswith(".step") or path.lower().endswith(".brp") or path.lower().endswith(".brep"):
                Part.show(Part.read(path))
            elif path.lower().endswith(".fcstd"):
                FreeCADGui.ActiveDocument.mergeProject(path)
            FreeCADGui.SendMsgToActiveView("ViewFit")

    def updatelibrary(self):
        CDBSApi(QueriesAPI.favComponents(), LIBRARYPATH)
        updateComponentsList(LIBRARYPATH)

    def setconfig(self):
        ConfigDialog().exec_()

    def showoptions(self):
        controls = [self.updatebutton,self.configbutton,self.formatLabel,self.fcstdCB,self.stepCB,self.stlCB]
        tree = [self.preview]
        if self.updatebutton.isVisible():
            for c in controls:
                c.hide()
            for c in tree:
                c.show()
            self.optbutton.setText(translate("CADBaseLibrary", "Options ⏷"))
        else:
            for c in controls:
                c.show()
            for c in tree:
                c.hide()
            self.optbutton.setText(translate("CADBaseLibrary", "Options ⏶"))

    def showpreview(self):
        if self.preview.isVisible():
            self.preview.hide()
            self.prevbutton.setText(translate("CADBaseLibrary", "Preview ⏷"))
        else:
            self.preview.show()
            self.prevbutton.setText(translate("CADBaseLibrary", "Preview ⏶"))



class ConfigDialog(QtGui.QDialog):
    def __init__(self):
        QtGui.QDialog.__init__(self)
        self.setObjectName("Config")
        self.resize(420, 250)
        self.verticalLayout = QtGui.QVBoxLayout(self)
        self.verticalLayout.setObjectName("verticalLayout")

        self.groupBox_3 = QtGui.QGroupBox(self)
        self.groupBox_3.setObjectName("groupBox_3")
        self.horizontalLayout_3 = QtGui.QHBoxLayout(self.groupBox_3)
        self.horizontalLayout_3.setObjectName("horizontalLayout_3")
        self.lineEdit_3 = QtGui.QLineEdit(self.groupBox_3)
        self.lineEdit_3.setObjectName("lineEdit_3")
        self.horizontalLayout_3.addWidget(self.lineEdit_3)
        self.pushButton_3 = QtGui.QPushButton(self.groupBox_3)
        self.pushButton_3.setObjectName("pushButton_3")
        self.horizontalLayout_3.addWidget(self.pushButton_3)
        self.verticalLayout.addWidget(self.groupBox_3)

        self.groupBox = QtGui.QGroupBox(self)
        self.groupBox.setObjectName("groupBox")
        self.horizontalLayout = QtGui.QHBoxLayout(self.groupBox)
        self.horizontalLayout.setObjectName("horizontalLayout")
        self.lineEdit = QtGui.QLineEdit(self.groupBox)
        self.lineEdit.setObjectName("lineEdit")
        self.horizontalLayout.addWidget(self.lineEdit)
        self.pushButton = QtGui.QPushButton(self.groupBox)
        self.pushButton.setObjectName("pushButton")
        self.horizontalLayout.addWidget(self.pushButton)
        self.verticalLayout.addWidget(self.groupBox)

        self.groupBox_2 = QtGui.QGroupBox(self)
        self.groupBox_2.setObjectName("groupBox_2")
        self.verticalLayout_2 = QtGui.QVBoxLayout(self.groupBox_2)
        self.verticalLayout_2.setObjectName("verticalLayout_2")
        self.lineEdit_2 = QtGui.QLineEdit(self.groupBox_2)
        self.lineEdit_2.setObjectName("lineEdit_2")
        self.verticalLayout_2.addWidget(self.lineEdit_2)
        self.label = QtGui.QLabel(self.groupBox_2)
        self.label.setObjectName("label")
        self.verticalLayout_2.addWidget(self.label)
        self.verticalLayout.addWidget(self.groupBox_2)

        self.groupBox_4 = QtGui.QGroupBox(self)
        self.groupBox_4.setObjectName("groupBox_4")
        self.verticalLayout_4 = QtGui.QVBoxLayout(self.groupBox_4)
        self.verticalLayout_4.setObjectName("verticalLayout_4")
        self.lineEdit_4 = QtGui.QLineEdit(self.groupBox_4)
        self.lineEdit_4.setEchoMode(QtGui.QLineEdit.Password)
        self.lineEdit_4.setObjectName("lineEdit_4")
        self.verticalLayout_4.addWidget(self.lineEdit_4)
        self.label = QtGui.QLabel(self.groupBox_4)
        self.label.setObjectName("label")
        self.verticalLayout_4.addWidget(self.label)
        self.verticalLayout.addWidget(self.groupBox_4)

        self.buttonBox = QtGui.QDialogButtonBox(self)
        self.buttonBox.setOrientation(QtCore.Qt.Horizontal)
        self.buttonBox.setStandardButtons(QtGui.QDialogButtonBox.Cancel|QtGui.QDialogButtonBox.Ok)
        self.buttonBox.setObjectName("buttonBox")
        self.verticalLayout.addWidget(self.buttonBox)

        self.retranslateUi()
        QtCore.QObject.connect(self.buttonBox, QtCore.SIGNAL("accepted()"), self.accept)
        QtCore.QObject.connect(self.buttonBox, QtCore.SIGNAL("rejected()"), self.reject)
        QtCore.QObject.connect(self.pushButton, QtCore.SIGNAL("clicked()"), self.setdefaulturl)
        QtCore.QObject.connect(self.pushButton_3, QtCore.SIGNAL("clicked()"), self.changepath)
        QtCore.QMetaObject.connectSlotsByName(self)

        librarypath = param.GetString('destination','')
        self.lineEdit_3.setText(librarypath)

    def retranslateUi(self):
        self.setWindowTitle(QtGui.QApplication.translate("CADBaseLibrary", "CADBase library configuration"))
        self.groupBox.setTitle(QtGui.QApplication.translate("CADBaseLibrary", "Pull server (where you get your updates from)"))
        self.lineEdit.setToolTip(QtGui.QApplication.translate("CADBaseLibrary", "Enter the URL of the pull server here"))
        self.pushButton.setToolTip(QtGui.QApplication.translate("CADBaseLibrary", "Use the official CADBase API"))
        self.pushButton.setText(QtGui.QApplication.translate("CADBaseLibrary", "use official"))
        self.groupBox_2.setTitle(QtGui.QApplication.translate("CADBaseLibrary", "Username"))
        self.lineEdit_2.setToolTip(QtGui.QApplication.translate("CADBaseLibrary", "Enter yout username from the CADBase"))
        self.label.setText(QtGui.QApplication.translate("CADBaseLibrary", "Warning: You need write permission on this server"))
        self.groupBox_3.setTitle(QtGui.QApplication.translate("CADBaseLibrary", "Library path"))
        self.lineEdit_3.setToolTip(QtGui.QApplication.translate("CADBaseLibrary", "Enter the path to your CADBase library"))
        self.pushButton_3.setToolTip(QtGui.QApplication.translate("CADBaseLibrary", "Browse to your path library"))
        self.pushButton_3.setText(QtGui.QApplication.translate("CADBaseLibrary", "..."))
        self.groupBox_4.setTitle(QtGui.QApplication.translate("CADBaseLibrary", "Password"))
        self.lineEdit_4.setToolTip(QtGui.QApplication.translate("CADBaseLibrary", "Enter yout password from the CADBase"))

    def setdefaulturl(self):
        self.lineEdit.setText(cdbs_api)

    def changepath(self):
        librarypath = param.GetString('destination','')
        np = QtGui.QFileDialog.getExistingDirectory(self,"Local location of your existing CADBase library",librarypath)
        if np:
            self.lineEdit_3.setText(np)

    def accept(self):
        if self.lineEdit.text():
            param.SetString('api-url',self.lineEdit.text())
        if self.lineEdit_3.text():
            param.SetString('destination',self.lineEdit_3.text())

        if self.lineEdit_2.text() and self.lineEdit_4.text():
            username, password = (self.lineEdit_2.text(), self.lineEdit_4.text())
            CDBSAuth(username, password)

        # FreeCAD.Console.PrintWarning(param.GetString('api-url',''))
        # FreeCAD.Console.PrintWarning(param.GetString('auth-token',''))

        QtGui.QDialog.accept(self)

if QtCore.QDir(LIBRARYPATH).exists():
    m = FreeCADGui.getMainWindow()
    w = m.findChild(QtGui.QDockWidget,"CADBaseLibrary")
    if w:
        if hasattr(w,"isVisible"):
            if w.isVisible():
                w.hide()
            else:
                w.show()
        else:
            # something went wrong with our widget... Recreate it
            del w
            m.addDockWidget(QtCore.Qt.RightDockWidgetArea,ExpDockWidget(LIBRARYPATH))
    else:
        m.addDockWidget(QtCore.Qt.RightDockWidgetArea,ExpDockWidget(LIBRARYPATH))
else:
    print("Library path ", LIBRARYPATH, "not found.")


def updateComponentsList(LIBRARYPATH):

    data = parsingGpl(LIBRARYPATH)
    if isinstance(data, SimpleNamespace):

        if len(data.components) == 0:

            FreeCAD.Console.PrintWarning('You don\'t have favorite components\n')

        else:

            for component in data.components:
                FreeCAD.Console.PrintWarning(component.uuid + '\n')
                new_dir = LIBRARYPATH + "/" + component.name + ' (from ' + component.ownerUser.username + ')'
                # FreeCAD.Console.PrintWarning(new_dir)

                if not os.path.exists(new_dir):
                    os.mkdir(new_dir)
                # else:
                #     FreeCAD.Console.PrintWarning(new_dir)
                #     FreeCAD.Console.PrintWarning(' : exists\n')

                if not os.path.isdir(new_dir):
                    os.remove(new_dir)
                    os.mkdir(new_dir)
                # else:
                #     FreeCAD.Console.PrintWarning(new_dir)
                #     FreeCAD.Console.PrintWarning(' : is a directory\n')

                new_info_file = new_dir + "/component"

                if os.path.exists(new_info_file):
                    if os.path.isdir(new_info_file):
                        os.rmdir(new_info_file)
                    else:
                        os.remove(new_info_file)

                f = open(new_info_file, "x")
                data = json.dumps(component, default=lambda o: o.__dict__, indent=4)
                f.write(data)
                f.close()
                # FreeCAD.Console.PrintWarning(new_info_file + '\n')

        # data_file = open(new_info_file, 'r')
        # component_data = json.loads(data_file.read(), object_hook=lambda d: SimpleNamespace(**d))
        # FreeCAD.Console.PrintWarning(component_data.uuid)
        # data_file.close()
    FreeCAD.Console.PrintWarning('Finished\n')

def updateComponent(LIBRARYPATH, component_path):

    # FreeCAD.Console.PrintWarning('updateComponent start\n')
    data = parsingGpl(LIBRARYPATH)
    if isinstance(data, SimpleNamespace):

        if len(data.componentModifications) == 0:

            FreeCAD.Console.PrintWarning('No modifications for the component\n')

        else:

            for modification in data.componentModifications:
                new_dir = component_path + "/" + modification.modificationName
                # FreeCAD.Console.PrintWarning(new_dir)

                if not os.path.exists(new_dir):
                    os.mkdir(new_dir)
                # else:
                #     FreeCAD.Console.PrintWarning(new_dir)
                #     FreeCAD.Console.PrintWarning(' : exists\n')

                if not os.path.isdir(new_dir):
                    os.remove(new_dir)
                    os.mkdir(new_dir)
                # else:
                #     FreeCAD.Console.PrintWarning(new_dir)
                #     FreeCAD.Console.PrintWarning(' : is a directory\n')

                new_info_file = new_dir + "/modification"

                if os.path.exists(new_info_file):
                    if os.path.isdir(new_info_file):
                        os.rmdir(new_info_file)
                    else:
                        os.remove(new_info_file)

                f = open(new_info_file, "x")
                data = json.dumps(modification, default=lambda o: o.__dict__, indent=4)
                f.write(data)
                f.close()
                # FreeCAD.Console.PrintWarning(new_info_file + '\n')
    FreeCAD.Console.PrintWarning('Finished\n')

def updateComponentModificaion(LIBRARYPATH, modification_path, modification_uuid):

    # FreeCAD.Console.PrintWarning('Getting files\n')

    data = parsingGpl(LIBRARYPATH)
    if isinstance(data, SimpleNamespace):

        if len(data.componentModificationFilesets) == 0:

            FreeCAD.Console.PrintWarning('Fileset not found for FreeCAD\n')

        else:

            CDBSApi(QueriesAPI.filesetFiles(data.componentModificationFilesets[0].uuid), LIBRARYPATH)

            data = parsingGpl(LIBRARYPATH)
            if isinstance(data, SimpleNamespace):

                if len(data.componentModificationFilesetFiles) == 0:
                    FreeCAD.Console.PrintWarning('No files in fileset\n')

                else:

                    urls = []
                    fns = []

                    for file_of_fileset in data.componentModificationFilesetFiles:
                        urls.append(file_of_fileset.downloadUrl)
                        fns.append(modification_path + "/" + file_of_fileset.filename)

                    inputs = zip(urls, fns)
                    download_parallel(inputs)
                    FreeCAD.Console.PrintWarning('Download is completed (')
                    FreeCAD.Console.PrintWarning(len(urls))
                    FreeCAD.Console.PrintWarning(' file(s)\n')

    FreeCAD.Console.PrintWarning('Finished\n')

def download_parallel(args):
    # FreeCAD.Console.PrintWarning('Start download data\n')

    t0 = time.time()

    results = ThreadPool(cpu_count() - 1).imap_unordered(get_file, args)

    for result in results:
        FreeCAD.Console.PrintWarning('\npath: ')
        FreeCAD.Console.PrintWarning(result[0])
        FreeCAD.Console.PrintWarning(' time (s): ')
        FreeCAD.Console.PrintWarning(result[1])

    FreeCAD.Console.PrintWarning('\nTotal time:')
    FreeCAD.Console.PrintWarning(time.time() - t0)
    FreeCAD.Console.PrintWarning('\n')

def get_file(args):
    t0 = time.time()
    url, filepath = args[0], args[1]
    manager = QtNetwork.QNetworkAccessManager()

    try:
        request = QtNetwork.QNetworkRequest(QtCore.QUrl(url))
        # request.setRawHeader(b"Content-Type", b"application/json");
        request.setRawHeader(b'User-Agent', user_agent)

        reply = manager.get(request)
        loop = QtCore.QEventLoop()
        reply.finished.connect(loop.quit)
        loop.exec_()

        if reply.error() == QtNetwork.QNetworkReply.NoError:

            responseData = reply.readAll()

            with open(filepath, 'wb') as f:
                f.write(responseData)

            return (filepath, time.time() - t0)
        else:
            FreeCAD.Console.PrintWarning('Error')
    except Exception as e:
        FreeCAD.Console.PrintWarning('Exception in download file: ')
        FreeCAD.Console.PrintWarning(e)

class CDBSApi:

    def __init__(self, query, LIBRARYPATH):

        FreeCAD.Console.PrintWarning('Getting data...\n')
        self.doRequest(query, LIBRARYPATH)


    def doRequest(self, query, LIBRARYPATH):

        api_url = param.GetString('api-url', '')
        req = QtNetwork.QNetworkRequest(QtCore.QUrl(api_url))

        auth_header = 'Bearer ' + param.GetString('auth-token', '')
        header = {'Authorization': auth_header}

        req.setRawHeader(b"Content-Type", content_type);
        req.setRawHeader(b"Authorization", auth_header.encode());

        body = json.dumps(query).encode('utf-8')

        self.nam = QtNetwork.QNetworkAccessManager()
        reply = self.nam.post(req, body)
        loop = QtCore.QEventLoop()
        reply.finished.connect(loop.quit)
        loop.exec_()
        self.handleResponse(reply, LIBRARYPATH)

    def handleResponse(self, reply, LIBRARYPATH):

        new_info_file = LIBRARYPATH + "/" + RESPONSEFILE

        if os.path.exists(new_info_file):
            if os.path.isdir(new_info_file):
                os.rmdir(new_info_file)
            else:
                os.remove(new_info_file)

        er = reply.error()

        if er == QtNetwork.QNetworkReply.NoError:
            if reply.attribute(QtNetwork.QNetworkRequest.HttpStatusCodeAttribute) == 200:

                bytes_string = reply.readAll()
                # FreeCAD.Console.PrintWarning(bytes_string)
                with open(new_info_file, 'wb') as file:
                    file.write(bytes_string)

                FreeCAD.Console.PrintWarning('Success\n')

            else:
                FreeCAD.Console.PrintWarning('Failed, status code: ')
                FreeCAD.Console.PrintWarning(reply.attribute(QtNetwork.QNetworkRequest.HttpStatusCodeAttribute))

        else:
            FreeCAD.Console.PrintWarning("Error occured: ")
            FreeCAD.Console.PrintWarning(er)
            FreeCAD.Console.PrintWarning('\n')
            FreeCAD.Console.PrintWarning(reply.errorString())
            FreeCAD.Console.PrintWarning('\n')

def parsingGpl(LIBRARYPATH):
    FreeCAD.Console.PrintWarning('Data processing, please wait.\n')
    response_path = LIBRARYPATH + "/" + RESPONSEFILE
    # FreeCAD.Console.PrintWarning(response_path + '\n')

    if os.path.exists(response_path):

        f = open(response_path, "rb", buffering=0)

        x = json.loads(f.readall(), object_hook=lambda d: SimpleNamespace(**d))

        if x.data == None:

            FreeCAD.Console.PrintWarning('Error occured: ')

            for error in x.errors:
                FreeCAD.Console.PrintWarning(error.message + '\n')

        else:
            return x.data

    else:

        FreeCAD.Console.PrintWarning('No file with response\n')

    FreeCAD.Console.PrintWarning('Failed\n')

class CDBSAuth:

    def __init__(self, username, password):

        FreeCAD.Console.PrintWarning("Getting a new token, please wait.\n")

        query = {'user': { 'username': username, 'password': password}}

        self.doRequest(query)


    def doRequest(self, query):

        req = QtNetwork.QNetworkRequest(QtCore.QUrl(api_login))

        req.setRawHeader(b"Content-Type", content_type);

        body = json.dumps(query).encode('utf-8')
        self.nam = QtNetwork.QNetworkAccessManager()
        reply = self.nam.post(req, body)
        loop = QtCore.QEventLoop()
        reply.finished.connect(loop.quit)
        loop.exec_()
        self.handleResponse(reply)

    def handleResponse(self, reply):

        er = reply.error()

        if er == QtNetwork.QNetworkReply.NoError:

            bytes_string = reply.readAll()
            token = json.loads(str(bytes_string, 'utf-8'))
            # FreeCAD.Console.PrintWarning(token["bearer"])
            param.SetString('auth-token', token["bearer"])

            FreeCAD.Console.PrintWarning('Success\n')

        else:
            FreeCAD.Console.PrintWarning("Error occured: ")
            FreeCAD.Console.PrintWarning(er)
            FreeCAD.Console.PrintWarning('\n')
            FreeCAD.Console.PrintWarning(reply.errorString())
            FreeCAD.Console.PrintWarning('\n')

class QueriesAPI:
    def favComponents():
        return {"query" : """{
          components (args: {
            favorite: true
          }) {
            uuid
            name
            ownerUser {
              uuid
              username
            }
            imageFile {
              uuid
              filename
              downloadUrl # preview для отображения иконки компонента
            }
          }
        }"""}

    def componentModifications(object_uuid):
        query = {"query" : """{ \
          componentModifications (args: { \
            componentUuid: \"""" + object_uuid + """\"
            # programId: 42
          }) { \
            uuid \
            modificationName \
            # filesetsForProgram {
            #   uuid
            # }
          } \
        }"""}

        return query

    def targetFileset(object_uuid):
        query = {"query" : """{ \
          componentModificationFilesets (args: { \
            modificationUuid: \"""" + object_uuid + """\"
            programIds: 42 \
          }) { \
            uuid \
          } \
        }"""}

        return query

    def filesetFiles(object_uuid):
        query = {"query" : """{ \
          componentModificationFilesetFiles (args: { \
            filesetUuid: \"""" + object_uuid + """\"
          }) { \
            uuid \
            filename \
            downloadUrl \
          } \
        }"""}

        return query
